[DOCUMENT]
TITLE: 退款幂等

[SECTION]
TITLE: 重复提交

[REQUIREMENT]
UID: REQ-PAY-004
TITLE: 同一幂等键的重复退款请求返回同一退款单
STATUS: proposed
OWNER: team-payments
PROJECT: PAY
PRIORITY: P1
CATEGORY: functional
REVISION: 2
BRIEF: requirements/briefs/REQ-PAY-004.md
SOURCE: chat,meeting

[RELATION]
Type: allocated_to
Value: MOD-PAY-REFUND

[RELATION]
Type: constrained_by
Value: ADR-PAY-003

[RELATION]
Type: verified_by
Value: TEST-PAY-004

[RELATION]
Type: verified_by
Value: TEST-PAY-005
